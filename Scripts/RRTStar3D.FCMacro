import FreeCAD
import Part
import Mesh
import random
import math
import FreeCADGui

doc = FreeCAD.ActiveDocument

EPS = 15
MAX_ITER = 5000
GOAL_THRESHOLD = 20
BRANCH_RADIUS = 0.25
LINE_BIAS_WIDTH = 80
x_max = 400
z_max = 400

sel = FreeCADGui.Selection.getSelectionEx()

if len(sel) < 2:
    raise Exception("Please select two vertices or points")

connector1_pos = sel[0].SubObjects[0].Point
connector2_pos = sel[1].SubObjects[0].Point

direction = connector2_pos.sub(connector1_pos)
direction.normalize()

connector1_normal = direction
connector2_normal = direction.negative()

start_offset = connector1_pos + connector1_normal.multiply(EPS)
goal_offset  = connector2_pos + connector2_normal.multiply(EPS)

start_pos = [start_offset.x,start_offset.y,start_offset.z]
goal_pos  = [goal_offset.x,goal_offset.y,goal_offset.z]

y_plane = start_pos[1]

class Node:
    def __init__(self,x,y,z,parent=None,cost=0):
        self.x = x
        self.y = y
        self.z = z
        self.parent = parent
        self.cost = cost

    def position(self):
        return [self.x,self.y,self.z]

def dist(a,b):
    return math.sqrt(
        (a[0]-b[0])**2 +
        (a[1]-b[1])**2 +
        (a[2]-b[2])**2
    )

def point_to_line_distance(p,a,b):
    ax,az = a[0],a[2]
    bx,bz = b[0],b[2]
    px,pz = p[0],p[2]
    num = abs((bz-az)*px - (bx-ax)*pz + bx*az - bz*ax)
    den = math.sqrt((bz-az)**2 + (bx-ax)**2)
    return num/den

def steer(qnear,qrand):
    dx = qrand[0]-qnear[0]
    dz = qrand[2]-qnear[2]
    d = math.sqrt(dx*dx + dz*dz)
    if d < EPS:
        return qrand
    scale = EPS/d
    return [
        qnear[0] + dx*scale,
        y_plane,
        qnear[2] + dz*scale
    ]

obstacles = []

for obj in doc.Objects:
    if obj.TypeId == "Mesh::Feature" and obj.Name != "Surface":
        obstacles.append(obj)

bbox_vis = []
obstacle_boxes = []

bb_group = doc.getObject("BlackBoxes")

if bb_group is None:
    bb_group = doc.addObject("App::DocumentObjectGroup", "BlackBoxes")

for obj in obstacles:

    bb = obj.Mesh.BoundBox

    box = Part.makeBox(
        bb.XLength,
        bb.YLength,
        bb.ZLength,
        FreeCAD.Vector(bb.XMin, bb.YMin, bb.ZMin)
    )

    vis = doc.addObject("Part::Feature","BBox")
    vis.Shape = box
    bbox_vis.append(vis)

    for v in bbox_vis:
        v.ViewObject.DisplayMode = "Wireframe"
        v.ViewObject.LineColor = (1.0,0.0,0.0)
        bb_group.addObject(v)

    expanded = FreeCAD.BoundBox(
        bb.XMin - BRANCH_RADIUS,
        bb.YMin - BRANCH_RADIUS,
        bb.ZMin - BRANCH_RADIUS,
        bb.XMax + BRANCH_RADIUS,
        bb.YMax + BRANCH_RADIUS,
        bb.ZMax + BRANCH_RADIUS
    )

    obstacle_boxes.append(expanded)

def line_intersects_bbox(p1,p2,bbox):

    d = dist(p1,p2)
    steps = int(d / (BRANCH_RADIUS * 0.25)) + 1

    for i in range(steps+1):

        t = i/steps

        x = p1[0] + (p2[0]-p1[0])*t
        y = p1[1] + (p2[1]-p1[1])*t
        z = p1[2] + (p2[2]-p1[2])*t

        if (bbox.XMin <= x <= bbox.XMax and
            bbox.YMin <= y <= bbox.YMax and
            bbox.ZMin <= z <= bbox.ZMax):
            return True

    return False

def is_collision(p1,p2):

    for bbox in obstacle_boxes:
        if line_intersects_bbox(p1,p2,bbox):
            return True

    return False

def sample_point():

    while True:

        qrand = [
            random.uniform(0,x_max),
            y_plane,
            random.uniform(0,z_max)
        ]

        d = point_to_line_distance(qrand,start_pos,goal_pos)

        if d < LINE_BIAS_WIDTH or random.random() < 0.2:
            return qrand

def create_stable_spline(points):

    params = [0]

    for i in range(1,len(points)):
        d = points[i].distanceToPoint(points[i-1])
        params.append(params[-1] + d)

    spline = Part.BSplineCurve()
    spline.interpolate(points,Parameters=params)

    return spline

def clean_points(points, tol=1e-6):

    cleaned = [points[0]]

    for p in points[1:]:
        if p.distanceToPoint(cleaned[-1]) > tol:
            cleaned.append(p)

    return cleaned

def smooth_path(path, iterations=100):

    import random

    path = path.copy()

    for _ in range(iterations):

        if len(path) <= 2:
            break

        i = random.randint(0, len(path) - 2)
        j = random.randint(i + 1, len(path) - 1)

        if j == i + 1:
            continue

        p1 = path[i]
        p2 = path[j]

        if dist(p1,p2) > 50:
            continue

        if not is_collision(p1, p2):
            path = path[:i+1] + path[j:]

    return path

nodes = []
nodes.append(Node(start_pos[0],start_pos[1],start_pos[2]))

goal_node = None

for i in range(MAX_ITER):

    qrand = goal_pos if random.random() < 0.2 else sample_point()

    nearest = min(nodes,key=lambda n: dist(n.position(),qrand))

    qnear = nearest.position()
    qnew = steer(qnear,qrand)

    if is_collision(qnear,qnew):
        continue

    new_node = Node(qnew[0],qnew[1],qnew[2],nearest)

    nodes.append(new_node)

    if dist(qnew,goal_pos) < GOAL_THRESHOLD:

        goal_node = Node(goal_pos[0],goal_pos[1],goal_pos[2],new_node)

        print("Goal reached")
        break

if goal_node is None:
    raise Exception("Failed to reach goal")

path = []

current = goal_node

while current:

    path.append(current.position())
    current = current.parent

path.reverse()

path.insert(0,[connector1_pos.x,connector1_pos.y,connector1_pos.z])
path.insert(1,[start_offset.x,start_offset.y,start_offset.z])

path.append([goal_offset.x,goal_offset.y,goal_offset.z])
path.append([connector2_pos.x,connector2_pos.y,connector2_pos.z])

original_path = path.copy()
smoothed_path = smooth_path(path, 100)

collision_found = False

for i in range(len(smoothed_path)-1):
    if is_collision(smoothed_path[i], smoothed_path[i+1]):
        collision_found = True
        break

if collision_found:
    path = original_path
    print("Collision found")
else:
    path = smoothed_path
    print("Smoothened Path")
points = [FreeCAD.Vector(p[0],p[1],p[2]) for p in path]

points = clean_points(points)

raw_points = [FreeCAD.Vector(p[0],p[1],p[2]) for p in points]

if len(raw_points) >= 2:

    raw_edges = []

    for i in range(len(raw_points)-1):
        e = Part.makeLine(raw_points[i], raw_points[i+1])
        raw_edges.append(e)

    raw_wire = Part.Wire(raw_edges)

    raw_obj = doc.addObject("Part::Feature","RawRRTPath")
    raw_obj.Shape = raw_wire

    raw_obj.ViewObject.LineColor = (0.0,1.0,0.0)  # Green
    raw_obj.ViewObject.LineWidth = 2

point_group = doc.getObject("SplinePoints")

# if point_group is None:
    # point_group = doc.addObject("App::DocumentObjectGroup","SplinePoints")

# for i,p in enumerate(points):

    # v = doc.addObject("Part::Vertex", f"SplinePoint_{i}")
    # v.X = p.x
    # v.Y = p.y
    # v.Z = p.z

    # v.ViewObject.PointColor = (0.0,0.0,1.0)
    # v.ViewObject.PointSize = 6

    # point_group.addObject(v)

# if len(points) < 2:
    # raise Exception("Not enough points for spline")

# spline = create_stable_spline(points)

# edge = spline.toShape()

# path_obj = doc.addObject("Part::Feature","HarnessSpline")
# path_obj.Shape = edge

# wire = Part.Wire([edge])

# start_param = spline.FirstParameter

# start_point = spline.value(start_param)

# tangent = spline.tangent(start_param)[0]
# tangent.normalize()

# circle = Part.makeCircle(BRANCH_RADIUS,start_point,tangent)

# profile = Part.Wire([circle])

# pipe = wire.makePipeShell([profile],True,False)

# pipe_obj = doc.addObject("Part::Feature","BranchPipe")
# pipe_obj.Shape = pipe

doc.recompute()

print("Path created with",len(points),"points")
