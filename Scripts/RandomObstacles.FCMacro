import FreeCAD
import Mesh
import os
import random
from math import radians
import Part

# -----------------------------
# DOCUMENT SETUP
# -----------------------------
doc = FreeCAD.ActiveDocument
if doc is None:
    doc = FreeCAD.newDocument("RRTScene")

# Directory of the macro
script_dir = os.path.dirname(os.path.abspath(__file__))

# Go up one level → Advanced_Harness_Routing_Planner
project_dir = os.path.dirname(script_dir)

# Models folder
models_dir = os.path.join(project_dir, "Models")

points_group = doc.getObject("ReferencePoints")

if points_group is None:
    points_group = doc.addObject("App::DocumentObjectGroup", "ReferencePoints")
# -----------------------------
# STL PATHS
# -----------------------------
connector1_path = os.path.join(models_dir, "BXDU-2-d12-H20.stl")
connector2_path = os.path.join(models_dir, "BXDR-M1-P5J-d8.stl")
connector3_path = os.path.join(models_dir, "SC8UU-D.stl")
housing_path = os.path.join(models_dir, "housing.stl")
surface_path = os.path.join(models_dir, "gorilla_heightmap.stl")

# -----------------------------
# WORKSPACE LIMITS
# -----------------------------
workspace = {
    "xmin": 0, "xmax": 180,
    "ymin": 0, "ymax": 0,   # Y fixed at 0
    "zmin": 0, "zmax": 350
}

# -----------------------------
# HELPER FUNCTIONS
# -----------------------------
def random_position():
    x = random.uniform(workspace["xmin"], workspace["xmax"])
    y = 0
    z = random.uniform(workspace["zmin"], workspace["zmax"])
    return FreeCAD.Vector(x, y, z)

def import_stl(path, name, scalex, scaley, scalez, position=None, rotation=None, color=None, transparency=0, create_point=True):
    mesh = Mesh.Mesh(path)
    mat = FreeCAD.Matrix()
    mat.scale(scalex, scaley, scalez)
    mesh.transform(mat)

    obj = doc.addObject("Mesh::Feature", name)
    obj.Mesh = mesh

    if position:
        obj.Placement.Base = position
    else:
        obj.Placement.Base = random_position()

    if rotation:
        obj.Placement.Rotation = rotation
        
    if color:
        obj.ViewObject.ShapeColor = color
        obj.ViewObject.Transparency = transparency

    # -----------------------------
    # CREATE POINT OBJECT
    # -----------------------------
    if create_point:
        point = doc.addObject("Part::Vertex", f"Point_{name}")
        point.X = obj.Placement.Base.x
        point.Y = obj.Placement.Base.y
        point.Z = obj.Placement.Base.z
        
        point.ViewObject.PointSize = 8
        point.ViewObject.PointColor = (1.0, 0.0, 0.0)
        points_group.addObject(point)

    return obj
    
# -----------------------------
# LOAD SURFACE (UNDER EVERYTHING)
# -----------------------------
rotation = FreeCAD.Rotation(FreeCAD.Vector(1,0,0), 90)  # degrees

surface_obj = import_stl(
    surface_path,
    "Surface",
    scalex=2,scaley=1,scalez=1,
    position=FreeCAD.Vector(0,-2,400),
    rotation=FreeCAD.Rotation(FreeCAD.Vector(1,0,0), 270),
    color=(0.85, 0.65, 0.13),  # ochre yellow
    transparency=20,
    create_point=False
)

# -----------------------------
# LOAD FIXED CONNECTORS
# -----------------------------
connector1_obj = import_stl(
    connector1_path,
    "Connector1",
    scalex=0.1,scaley=0.1,scalez=0.1,
    position=FreeCAD.Vector(10, 0, 10),
    color = (0.2, 0.4, 1.0), 
    transparency=0,
    create_point=True
)

# Fixed connector 2
connector2_obj = import_stl(
    connector2_path,
    "Connector2",
    scalex=0.1,scaley=0.1,scalez=0.1,
    position=FreeCAD.Vector(100, 0, 380),
    color = (0.2, 0.4, 1.0), 
    transparency=0,
    create_point=True
)

# -----------------------------
# LOAD RANDOM Housings
# -----------------------------
NUM_HOUSINGS = 15
for i in range(NUM_HOUSINGS):
    import_stl(housing_path, f"Housing_{i+1}", 2.0,2.0,2.0)

# -----------------------------
# LOAD RANDOM Connectors
# -----------------------------
NUM_CONNECTOR = 30
for i in range(NUM_CONNECTOR):
    import_stl(connector3_path, f"Connector3_{i+1}", 0.1,0.1,0.1, rotation=FreeCAD.Rotation(FreeCAD.Vector(1,0,0), 180),create_point=True)
    import_stl(connector1_path, f"Connector3_{i+1}", 0.1,0.1,0.1, create_point=True)
    import_stl(connector2_path, f"Connector3_{i+1}", 0.1,0.1,0.1, create_point=True)
# -----------------------------
# RECOMPUTE DOCUMENT
# -----------------------------
doc.recompute()
FreeCAD.Gui.updateGui() 
print("Objects loaded: fixed connectors, random housings, connector3, surface underneath.")
